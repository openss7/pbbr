IEEE8021-BRIDGE-MIB DEFINITIONS ::= BEGIN

-- ============================================================
-- MIB for IEEE 802.1D devices
-- ============================================================
IMPORTS
    IEEE8021BridgePortNumber, IEEE8021BridgePortType, 
    IEEE8021PbbComponentIdentifier, IEEE8021PriorityCodePoint, 
    IEEE8021PriorityValue, ieee802dot1mibs
        FROM IEEE8021-TC-MIB
    InterfaceIndexOrZero, ifGeneralInformationGroup, ifIndex
        FROM IF-MIB
    SnmpAdminString
        FROM SNMP-FRAMEWORK-MIB
    MODULE-COMPLIANCE, OBJECT-GROUP
        FROM SNMPv2-CONF
    systemGroup
        FROM SNMPv2-MIB
    Counter64, Integer32, MODULE-IDENTITY, OBJECT-TYPE
        FROM SNMPv2-SMI
    MacAddress, RowStatus, TimeInterval, TruthValue
        FROM SNMPv2-TC;

ieee8021BridgeMib MODULE-IDENTITY
    LAST-UPDATED "201102270000Z"
    ORGANIZATION 
        "IEEE 802.1 Working Group"
    CONTACT-INFO 
        "  WG-URL: http://grouper.ieee.org/groups/802/1/index.html
         WG-EMail: stds-802-1@ieee.org
         
          Contact: David Levi
           Postal: C/O IEEE 802.1 Working Group
                   IEEE Standards Association
                   445 Hoes Lane
                   P.O. Box 1331
                   Piscataway
                   NJ 08855-1331
                   USA
           E-mail: STDS-802-1-L@LISTSERV.IEEE.ORG"
    DESCRIPTION 
        "The Bridge MIB module for managing devices that support IEEE 
         802.1D.  This MIB module is derived from the IETF BRIDGE-MIB, 
         RFC 4188.
         
         Unless otherwise indicated, the references in this MIB module 
         are to IEEE Std 802.1Q-2011.
         
         Copyright (C) IEEE.
         This version of this MIB module is part of IEEE802.1Q; see the 
         draft itself for full legal notices."
    REVISION    "201102270000Z"
    DESCRIPTION 
        "Minor edits to contact information etc. as part of 2011 
         revision of IEEE Std 802.1Q."
    REVISION    "200810150000Z"
    DESCRIPTION 
        "Initial revision, derived from RFC 4188."
    ::= { ieee802dot1mibs 2 }

-- ============================================================
-- subtrees in the Bridge MIB
-- ============================================================

ieee8021BridgeNotifications OBJECT IDENTIFIER
    ::= { ieee8021BridgeMib 0 }

ieee8021BridgeObjects OBJECT IDENTIFIER
    ::= { ieee8021BridgeMib 1 }

ieee8021BridgeBase OBJECT IDENTIFIER
    ::= { ieee8021BridgeObjects 1 }

-- ============================================================
-- the ieee8021BridgeBase subtree
-- ============================================================
-- Implementation of the ieee8021BridgeBase subtree is mandatory 
-- for all bridges.
-- ============================================================

-- ============================================================
-- the ieee8021BridgeBaseTable
-- ============================================================
ieee8021BridgeBaseTable OBJECT-TYPE
    SYNTAX      SEQUENCE OF Ieee8021BridgeBaseEntry
    MAX-ACCESS  not-accessible
    STATUS      current
    DESCRIPTION 
        "A table that contains generic information about every bridge 
         component.  All writable objects in this table must be 
         persistent over power up restart/reboot."
    REFERENCE   
        "12.4.1"
    ::= { ieee8021BridgeBase 1 }

ieee8021BridgeBaseEntry OBJECT-TYPE
    SYNTAX      Ieee8021BridgeBaseEntry
    MAX-ACCESS  not-accessible
    STATUS      current
    DESCRIPTION 
        "A list of objects containing information for each bridge 
         component."
    INDEX       { ieee8021BridgeBaseComponentId }
    ::= { ieee8021BridgeBaseTable 1 }

Ieee8021BridgeBaseEntry ::= SEQUENCE {
    ieee8021BridgeBaseComponentId               IEEE8021PbbComponentIdentifier,
    ieee8021BridgeBaseBridgeAddress             MacAddress,
    ieee8021BridgeBaseNumPorts                  Integer32,
    ieee8021BridgeBaseComponentType             INTEGER,
    ieee8021BridgeBaseDeviceCapabilities        BITS,
    ieee8021BridgeBaseTrafficClassesEnabled     TruthValue,
    ieee8021BridgeBaseMmrpEnabledStatus         TruthValue,
    ieee8021BridgeBaseRowStatus                 RowStatus
}

ieee8021BridgeBaseComponentId OBJECT-TYPE
    SYNTAX      IEEE8021PbbComponentIdentifier
    MAX-ACCESS  not-accessible
    STATUS      current
    DESCRIPTION 
        "The component identifier is used to distinguish between the 
         multiple virtual bridge instances within a PBB.  In simple 
         situations where there is only a single component the default 
         value is 1."
    ::= { ieee8021BridgeBaseEntry 1 }

ieee8021BridgeBaseBridgeAddress OBJECT-TYPE
    SYNTAX      MacAddress
    MAX-ACCESS  read-create
    STATUS      current
    DESCRIPTION 
        "The MAC address used by this bridge when it must be referred to 
         in a unique fashion.  It is recommended that this be the 
         numerically smallest MAC address of all ports that belong to 
         this bridge.  However, it is only required to be unique.  When 
         concatenated with ieee8021SpanningTreePriority, a unique 
         BridgeIdentifier is formed, which is used in the Spanning Tree 
         Protocol.
         
         This object may not be modified while the corresponding 
         instance of ieee8021BridgeBaseRowStatus is active(1)).
         
         The value of this object MUST be retained across 
         reinitializations of the management system."
    REFERENCE   
        "12.4.1.1.3 a)"
    ::= { ieee8021BridgeBaseEntry 2 }

ieee8021BridgeBaseNumPorts OBJECT-TYPE
    SYNTAX      Integer32
    UNITS       "ports"
    MAX-ACCESS  read-only
    STATUS      current
    DESCRIPTION 
        "The number of ports controlled by this bridging entity."
    REFERENCE   
        "12.4.1.1.3 c)"
    ::= { ieee8021BridgeBaseEntry 3 }

ieee8021BridgeBaseComponentType OBJECT-TYPE
    SYNTAX      INTEGER { iComponent(1), bComponent(2), 
                    cVlanComponent(3), sVlanComponent(4), 
                    dBridgeComponent(5) }
    MAX-ACCESS  read-create
    STATUS      current
    DESCRIPTION 
        "Indicates the component type(s) of this bridge.  The following 
         component types are possible:
         
         iComponent(1) - An S-VLAN component of a Backbone Edge Bridge 
             which performs encapsulation of customer frames.
         
         bComponent(2) - An S-VLAN component of a Backbone Edge Bridge 
             which bundles backbone service instances int B-VLANs.
         
         cVlanComponent(3) - A C-VLAN component of an enterprise VLAN 
             bridge or of a Provider Bridge used to process C-tagged 
             frames.
         
         sVlanComponent(4) - An S-VLAN component of a Provider Bridge.
         
         dBridgeComponet(5) - A VLAN unaware component of an 802.1D 
             bridge.
         
         This object may not be modified while the corresponding 
         instance of ieee8021BridgeBaseRowStatus is active(1).
         
         The value of this object MUST be retained across 
         reinitializations of the management system."
    REFERENCE   
        "12.3 m)"
    ::= { ieee8021BridgeBaseEntry 4 }

ieee8021BridgeBaseDeviceCapabilities OBJECT-TYPE
    SYNTAX      BITS { dot1dExtendedFilteringServices(0), 
                    dot1dTrafficClasses(1), 
                    dot1qStaticEntryIndividualPOrt(2), 
                    dot1qIVLCapable(3), dot1qSVLCapable(4), 
                    dot1qHybridCapable(5), 
                    dot1qConfigurablePvidTagging(6), 
                    dot1dLocalVlanCapable(7) }
    MAX-ACCESS  read-create
    STATUS      current
    DESCRIPTION 
        "Indicates the optional parts of IEEE 802.1D and 802.1Q that are 
         implemented by this device and are manageable through this MIB.  
         Capabilities that are allowed on a per-port basis are indicated 
         in ieee8021BridgeBasePortCapabilities.
         
         dot1dExtendedFilteringServices(0),
             can perform filtering of individual multicast addresses 
             controlled by MMRP.
         dot1dTrafficClasses(1),
             can map user priority to multiple traffic classes.
         dot1qStaticEntryIndividualPort(2),
             dot1qStaticUnitcastReceivePort & 
             dot1qStaticMulticastReceivePort can represent non-zero 
             entries.
         dot1qIVLCapable(3),
             Independent VLAN Learning (IVL).
         dot1qSVLCapable(4),
             Shared VLAN Learning (SVL).
         dot1qHybridCapable(5),
             both IVL & SVL simultaneously.
         dot1qConfigurablePvidTagging(6),
             whether the implementation supports the ability to override 
             the default PVID setting and its egress status (VLAN-Tagged 
             or Untagged) on each port.
         dot1dLocalVlanCapable(7),
             can support multiple local bridges, outside of the scope of 
             802.1Q defined VLANs.
         
         This object may not be modified while the corresponding 
         instance of ieee8021BridgeBaseRowStatus is active(1).
         
         The value of this object MUST be retained across 
         reinitializations of the management system."
    REFERENCE   
        "12.10.1.1.3 b)"
    ::= { ieee8021BridgeBaseEntry 5 }

ieee8021BridgeBaseTrafficClassesEnabled OBJECT-TYPE
    SYNTAX      TruthValue
    MAX-ACCESS  read-create
    STATUS      current
    DESCRIPTION 
        "The value true(1) indicates that Traffic Classes are enabled on 
         this bridge.  When false(2), the bridge oeprates with a single 
         priority level for all traffic.
         
         This object may be modified while the corresponding instance of 
         ieee8021BridgeBaseRowStatus is active(1).
         
         The value of this object MUST be retained across 
         reinitializations of the management system."
    DEFVAL      { true }
    ::= { ieee8021BridgeBaseEntry 6 }

ieee8021BridgeBaseMmrpEnabledStatus OBJECT-TYPE
    SYNTAX      TruthValue
    MAX-ACCESS  read-create
    STATUS      current
    DESCRIPTION 
        "The administrative status requested by management for MMRP.  
         The value true(1) indicates that MMRP should be enabled on this 
         device, in all VLANs, on all ports for which it has not been 
         specifically disabled.  When false(2), MMRP is disabled, in all 
         VLANs and on all ports, and all MMRP packets will be forwarded 
         transparently.  This object affects both Applicant and 
         Registrar state machines.  A transition from false(2) to 
         true(1) will cause a reset of all MMRP state machines on all 
         ports.
         
         This object may be modified while the corresponding instance of 
         ieee8021BridgeBaseRowStatus is active(1).
         
         The value of this object MUST be retained across 
         reinitializations of the management system."
    DEFVAL      { true }
    ::= { ieee8021BridgeBaseEntry 7 }

ieee8021BridgeBaseRowStatus OBJECT-TYPE
    SYNTAX      RowStatus
    MAX-ACCESS  read-create
    STATUS      current
    DESCRIPTION 
        "The object indicates the status of an entry, and is used to 
         create/delete entries.
         
         The following objects must be set prior to making a new entry 
         active:
             ieee8021BridgeBaseBridgeAddress
             ieee8021BridgeBaseComponentType
             ieee8021BridgeBaseDeviceCapabilities
         It is recommended that these three objects not be allowed to be 
         modified while the corresponding instance of 
         ieee8021BridgeBaseRowStatus object is active(1).
         
         The following objects are not required to be set before making 
         a new entry active (they will take their defaults), and they 
         also may be modified while the corresponding instance of this 
         object is active(1):
             ieee8021BridgeBaseTrafficClassesEnabled
             ieee8021BridgeBaseMmrpEnabledStatus
         
         The value of this object and all corresponding instances of 
         other objects in this table MUST be retained across 
         reinitializations of the management system."
    ::= { ieee8021BridgeBaseEntry 8 }

-- ============================================================
-- The Generic Bridge Port Table
-- ============================================================
ieee8021BridgeBasePortTable OBJECT-TYPE
    SYNTAX      SEQUENCE OF Ieee8021BridgeBasePortEntry
    MAX-ACCESS  not-accessible
    STATUS      current
    DESCRIPTION 
        "A table that contains generic information about every port that 
         is associated with this bridge.  Transparent, and source-route 
         ports are included."
    REFERENCE   
        "12.4.2"
    ::= { ieee8021BridgeBase 4 }

ieee8021BridgeBasePortEntry OBJECT-TYPE
    SYNTAX      Ieee8021BridgeBasePortEntry
    MAX-ACCESS  not-accessible
    STATUS      current
    DESCRIPTION 
        "A list of objects containing information for each port of 
         the bridge."
    INDEX       { ieee8021BridgeBasePortComponentId, 
                  ieee8021BridgeBasePort }
    ::= { ieee8021BridgeBasePortTable 1 }

Ieee8021BridgeBasePortEntry ::= SEQUENCE {
    ieee8021BridgeBasePortComponentId               IEEE8021PbbComponentIdentifier,
    ieee8021BridgeBasePort                          IEEE8021BridgePortNumber,
    ieee8021BridgeBasePortIfIndex                   InterfaceIndexOrZero,
    ieee8021BridgeBasePortDelayExceededDiscards     Counter64,
    ieee8021BridgeBasePortMtuExceededDiscards       Counter64,
    ieee8021BridgeBasePortCapabilities              BITS,
    ieee8021BridgeBasePortTypeCapabilities          BITS,
    ieee8021BridgeBasePortType                      IEEE8021BridgePortType,
    ieee8021BridgeBasePortExternal                  TruthValue,
    ieee8021BridgeBasePortAdminPointToPoint         INTEGER,
    ieee8021BridgeBasePortOperPointToPoint          TruthValue,
    ieee8021BridgeBasePortName                      SnmpAdminString
}

ieee8021BridgeBasePortComponentId OBJECT-TYPE
    SYNTAX      IEEE8021PbbComponentIdentifier
    MAX-ACCESS  not-accessible
    STATUS      current
    DESCRIPTION 
        "The component identifier is used to distinguish between the 
         multiple virtual bridge instances within a PBB.  In simple 
         situations where there is only a single component the default 
         value is 1."
    ::= { ieee8021BridgeBasePortEntry 1 }

ieee8021BridgeBasePort OBJECT-TYPE
    SYNTAX      IEEE8021BridgePortNumber
    MAX-ACCESS  not-accessible
    STATUS      current
    DESCRIPTION 
        "The port number of the port for which this entry contains 
         bridge management information."
    REFERENCE   
        "12.4.2.1.2 a)"
    ::= { ieee8021BridgeBasePortEntry 2 }

ieee8021BridgeBasePortIfIndex OBJECT-TYPE
    SYNTAX      InterfaceIndexOrZero
    MAX-ACCESS  read-write
    STATUS      current
    DESCRIPTION 
        "The value of the instance of the IfIndex object, defined in the 
         IF-MIB, for the interface corresponding to this port, or the 
         value 0 if the port has not been bound to an underlying frame 
         source and sink.
         
         It is an implementation specific decision ase to whether this 
         object may be modified if it have been created or if 0 is a 
         legal value.
         
         The underlying IfEntry indexed by this column must be 
         persistent across reinitializations of the management system."
    ::= { ieee8021BridgeBasePortEntry 3 }

ieee8021BridgeBasePortDelayExceededDiscards OBJECT-TYPE
    SYNTAX      Counter64
    MAX-ACCESS  read-only
    STATUS      current
    DESCRIPTION 
        "The number of frames discarded by this port due to excessive 
         transit delay through the bridge.  It is incremented by both 
         transparent and source route bridges.
         
         Discontinuities in the value of the counter can occur at 
         re-initialization of the management system, and at other times 
         as indicated by the value of ifCounterDiscontinuityTime object 
         of the associated interface (if any)."
    REFERENCE   
        "12.6.1.1.3 f)"
    ::= { ieee8021BridgeBasePortEntry 4 }

ieee8021BridgeBasePortMtuExceededDiscards OBJECT-TYPE
    SYNTAX      Counter64
    MAX-ACCESS  read-only
    STATUS      current
    DESCRIPTION 
        "The number of frames dicarded by this port due to an excessive 
         size.  It is incremented by both transparent and source route 
         bridges.
         
         Discontinuities in the value of the counter can occur at 
         re-initialization of the management system, and at other times 
         as indicated by the value of ifCounterDiscontinuityTime object 
         of the associated interface (if any)."
    REFERENCE   
        "12.6.1.1.3 g)"
    ::= { ieee8021BridgeBasePortEntry 5 }

ieee8021BridgeBasePortCapabilities OBJECT-TYPE
    SYNTAX      BITS { dot1qDot1qTagging(0), 
                    dot1qConfigurableAcceptableFrameTypes(1), 
                    dot1qIngressFiltering(2) }
    MAX-ACCESS  read-only
    STATUS      current
    DESCRIPTION 
        "Indicates the parts of IEEE 802.1D and 802.1Q that are optional 
         on a per-port basis, that are implemented by this device, and 
         that are manageable through this MIB.
         
         dot1qDot1qTagging(0),
             supports 802.1Q VLAN tagging of frames and MVRP.
         dot1qConfigurableAcceptableFrameTypes(1),
             allows modified values of dot1qPortAcceptableFrameTypes.
         dot1qIngressFiltering(2),
             supports the discarding of any frame received on a Port 
             whose VLAN classification does not include that Port in its 
             Member set."
    REFERENCE   
        "12.10.1.1.3 c)"
    ::= { ieee8021BridgeBasePortEntry 6 }

ieee8021BridgeBasePortTypeCapabilities OBJECT-TYPE
    SYNTAX      BITS { customerVlanPort(0), providerNetworkPort(1), 
                    customerNetworkPort(2), customerEdgePort(3), 
                    customerBackbonePort(4), virtualInstancePort(5), 
                    dBridgePort(6) }
    MAX-ACCESS  read-only
    STATUS      current
    DESCRIPTION 
        "Indicates the capabilities of this port.  The corresponding 
         instance of ieee8021BridgeBasePortType can potentially take any 
         of the values for which the corresponding bit in this object is 
         1.  The possible port types are as follows:
         
         customerVlanPort(0),
             Indicates the port can be a C-tag aware port of an 
             enterprise VLAN aware bridge.
         providerNetworkPort(1),
             Indicates the port can be an S-tag aware port of a Provider 
             Bridge or Backbone Edge Bridge used for connections within 
             a PBN or PBBN.
         customerNetworkPort(2),
             Indicates the port can be an S-tag aware port of a Provider 
             Bridge or Backbone Edge Bridge used for connections to the 
             exterior of a PBN or PBBN.
         customerEdgePort(3),
             Indicates the port can be a C-tag aware port of a Provider 
             Bridge used for connections to the exterior of a PBN or 
             PBBN.
         customerBackbonePort(4),
             Indicates the port can be a I-tag aware port of a Backbone 
             Edge Bridge's B-component.
         virtualInstancePort(5),
             Indicates the port can be a virtual S-tag aware port within 
             a Backbone Edge Bridge's I-component which is responsible 
             for handling S-tagged traffic for a specific backbone 
             service instance.
         dBridgePort(6),
             Indicates the port can be a VLAN-unaware member of an 
             802.1D bridge."
    REFERENCE   
        "12.16.1.1.3 h4), 12.16.2.1/2, 12.13.1.1, 12.13.1.2, 12.15.2.1, 12.15.2.2"
    ::= { ieee8021BridgeBasePortEntry 7 }

ieee8021BridgeBasePortType OBJECT-TYPE
    SYNTAX      IEEE8021BridgePortType
    MAX-ACCESS  read-only
    STATUS      current
    DESCRIPTION 
        "The port type.  This value must be persistent over power up 
         restart/reboot."
    REFERENCE   
        "12.16.1.1.3 h4), 12.16.2.1/2, 12.13.1.1, 12.13.1.2, 12.15.2.1, 12.15.2.2"
    ::= { ieee8021BridgeBasePortEntry 8 }

ieee8021BridgeBasePortExternal OBJECT-TYPE
    SYNTAX      TruthValue
    MAX-ACCESS  read-only
    STATUS      current
    DESCRIPTION 
        "A boolean indicating whether the port is external.  A value of 
         true(1) means the port is external.  A value of false(2) means 
         the port is internal."
    REFERENCE   
        "12.16.1.1.3 h4)"
    ::= { ieee8021BridgeBasePortEntry 9 }

ieee8021BridgeBasePortAdminPointToPoint OBJECT-TYPE
    SYNTAX      INTEGER { forceTrue(1), forceFalse(2), auto(3) }
    MAX-ACCESS  read-write
    STATUS      current
    DESCRIPTION 
        "For a port running spanning tree, this object represents the 
         adminstrative point-to-point status of the LAN segment attached 
         to this port, using the enumeration values of 6.4.3.  A value 
         of forceTrue(1) indicates that this port should always be 
         treated as if it is connected to a point-to-point link.  A 
         value of forceFalse(2) indicates that this port should be 
         treated as having a shared media connection.  A value of 
         auto(3) indicates that this port is considered to have a 
         point-to-point link if it is an Aggregator and all of its 
         members are aggregatable, or if the MAC entity is configured 
         for full duplex operation, either through auto-negotiation or 
         by management means.  Manipulating this object changes the 
         underlying adminPointToPointMAC.
         
         For a VIP, the adminPointToPointMAC parameter controls the 
         mechanism by which the Default Backbone Destination parameter 
         for the VIP is determined.  For a backbone service instance 
         that includes only 2 VIPs, the value may be set to forceTrue(1) 
         which permits dynamic learning of the Default Backbone 
         Destination parameter.  For a backbone service instance that 
         includes more than 2 VIPs, the value must be set to 
         forceFalse(2) or auto(3).
         
         When this object is set to forceTrue(1) for a VIP, the Default 
         Backbone Destination parameter is modified by the subsequent 
         M_UNITDATA.indications as specified in 6.10.1 (and described in 
         26.4.1).  Whenever the parameter is set to forceFalse(2) or 
         auto(3), the value for the Default Backbone Destination 
         parameter is set to the Backbone Service Instance Group Address 
         for the VIP-ISID.
         
         The value of this object MUST be retained across 
         reinitialization of the management system."
    REFERENCE   
        "6.6.3, 6.10, 12.8.2.1.3 o), 12.8.2.3.2 f), 26.4.1"
    DEFVAL      { forceFalse }
    ::= { ieee8021BridgeBasePortEntry 10 }

ieee8021BridgeBasePortOperPointToPoint OBJECT-TYPE
    SYNTAX      TruthValue
    MAX-ACCESS  read-only
    STATUS      current
    DESCRIPTION 
        "For a port running spanning tree, this object represents the 
         operational point-to-point status of the LAN segment attached 
         to this port.  It indicates whether a port is considered to 
         have a point-to-point connection.  If adminPointToPointMAC is 
         set to auto(3), then the value of operPointToPointMAC is 
         determined in accordance with the specific procedures defined 
         for the MAC entity concerned, as defined in 6.5 of IEEE 802.1w.  
         The value is determined dynamically; that is, it is 
         re-evaluated whenever the value of adminPointToPointMAC 
         changes, and whenever the specific procedures defined for the 
         MAC entity evaluate a change in its point-to-point status.
         
         For a VIP, this object simply reflects the value of the 
         corresponding instance of 
         ieee8021BridgeBasePortAdminPointToPoint.  The value will be 
         true(1) if that object is forceTrue(1), and the value will be 
         false(2) if the value of that object is either forceFalse(2) or 
         auto(3)."
    REFERENCE   
        "6.6.3, 6.10, 12.8.2.1.3 p), 12.8.2.3.2 f), 26.4.1"
    ::= { ieee8021BridgeBasePortEntry 11 }

ieee8021BridgeBasePortName OBJECT-TYPE
    SYNTAX      SnmpAdminString
    MAX-ACCESS  read-only
    STATUS      current
    DESCRIPTION 
        "A text string of up to 32 characters, of locally determined 
         significance."
    REFERENCE   
        "12.4.2.1.3 a)"
    ::= { ieee8021BridgeBasePortEntry 12 }

-- ============================================================
-- the ieee8021BridgeTp subtree
-- ============================================================
-- This is implemented by those bridges that support the 
-- transparent bridging mode.  A transparent bridge will 
-- implement this subtree.
-- ============================================================

-- ============================================================
-- Port Table for Transparent Bridges
-- ============================================================

ieee8021BridgeTp OBJECT IDENTIFIER
    ::= { ieee8021BridgeObjects 2 }

ieee8021BridgeTpPortTable OBJECT-TYPE
    SYNTAX      SEQUENCE OF Ieee8021BridgeTpPortEntry
    MAX-ACCESS  not-accessible
    STATUS      current
    DESCRIPTION 
        "A table that contains information about every port that is 
         associated with this transparent bridge."
    REFERENCE   
        "12.4.2, C.4"
    ::= { ieee8021BridgeTp 1 }

ieee8021BridgeTpPortEntry OBJECT-TYPE
    SYNTAX      Ieee8021BridgeTpPortEntry
    MAX-ACCESS  not-accessible
    STATUS      current
    DESCRIPTION 
        "A list of objects containing information for each port of a 
         transparent bridge."
    INDEX       { ieee8021BridgeTpPortComponentId, 
                  ieee8021BridgeTpPortPort }
    ::= { ieee8021BridgeTpPortTable 1 }

Ieee8021BridgeTpPortEntry ::= SEQUENCE {
    ieee8021BridgeTpPortComponentId     IEEE8021PbbComponentIdentifier,
    ieee8021BridgeTpPortPort            IEEE8021BridgePortNumber,
    ieee8021BridgeTpPortPortMaxInfo     Integer32,
    ieee8021BridgeTpPortInFrames        Counter64,
    ieee8021BridgeTpPortOutFrames       Counter64,
    ieee8021BridgeTpPortInDiscards      Counter64
}

ieee8021BridgeTpPortComponentId OBJECT-TYPE
    SYNTAX      IEEE8021PbbComponentIdentifier
    MAX-ACCESS  not-accessible
    STATUS      current
    DESCRIPTION 
        "The component identifier is used to distinguish between the 
         multiple virtual bridge instances within a PBB.  In simple 
         situations where there is only a single component the default 
         value is 1."
    ::= { ieee8021BridgeTpPortEntry 1 }

ieee8021BridgeTpPortPort OBJECT-TYPE
    SYNTAX      IEEE8021BridgePortNumber
    MAX-ACCESS  not-accessible
    STATUS      current
    DESCRIPTION 
        "The port number of the port for which this entry contains 
         Transparent bridging management information."
    ::= { ieee8021BridgeTpPortEntry 2 }

ieee8021BridgeTpPortPortMaxInfo OBJECT-TYPE
    SYNTAX      Integer32
    MAX-ACCESS  read-only
    STATUS      current
    DESCRIPTION 
        "The maximum size of the INFO (non-MAC) field that this port 
         will receive or transmit."
    ::= { ieee8021BridgeTpPortEntry 3 }

ieee8021BridgeTpPortInFrames OBJECT-TYPE
    SYNTAX      Counter64
    MAX-ACCESS  read-only
    STATUS      current
    DESCRIPTION 
        "The number of frames that have been received by this port from 
         its segment.  Note that a frame received on the interface 
         corresponding to this port is only counted by this object if 
         and only if it is for a protocol being processed by the local 
         bridging function, including bridge management frames.
         
         Discontinuities in the value of the counter can occur at 
         re-initialization of the management system, and at other times 
         as indicated by the value of ifCounterDiscontinuityTime object 
         of the associated interface (if any)."
    REFERENCE   
        "12.6.1.1.3 a)"
    ::= { ieee8021BridgeTpPortEntry 4 }

ieee8021BridgeTpPortOutFrames OBJECT-TYPE
    SYNTAX      Counter64
    MAX-ACCESS  read-only
    STATUS      current
    DESCRIPTION 
        "The number of frames that have been transmitted by this port to 
         its segment.  Note that a frame transmitted on the interface 
         corresponding to this port is only counted by this object if 
         and only if it is for a protocol being processed by the local 
         bridging function, including bridge management frames.
         
         Discontinuities in the value of the counter can occur at 
         re-initialization of the management system, and at other times 
         as indicated by the value of ifCounterDiscontinuityTime object 
         of the associated interface (if any)."
    REFERENCE   
        "12.6.1.1.3 d)"
    ::= { ieee8021BridgeTpPortEntry 5 }

ieee8021BridgeTpPortInDiscards OBJECT-TYPE
    SYNTAX      Counter64
    MAX-ACCESS  read-only
    STATUS      current
    DESCRIPTION 
        "Count of received valid frames that were discarded (i.e., 
         filtered) by the Forwarding Process.
         
         Discontinuities in the value of the counter can occur at 
         re-initialization of the management system, and at other times 
         as indicated by the value of ifCounterDiscontinuityTime object 
         of the associated interface (if any)."
    REFERENCE   
        "12.6.1.1.3 c)"
    ::= { ieee8021BridgeTpPortEntry 6 }


-- ============================================================
-- the ieee8021BridgePriority subtree
-- ============================================================

-- ============================================================
-- Port Priority Table
-- ============================================================

ieee8021BridgePriority OBJECT IDENTIFIER
    ::= { ieee8021BridgeObjects 3 }

ieee8021BridgePortPriorityTable OBJECT-TYPE
    SYNTAX      SEQUENCE OF Ieee8021BridgePortPriorityEntry
    MAX-ACCESS  not-accessible
    STATUS      current
    DESCRIPTION 
        "A table that contains information about every port that is 
         associated with this transparent bridge."
    ::= { ieee8021BridgePriority 1 }

ieee8021BridgePortPriorityEntry OBJECT-TYPE
    SYNTAX      Ieee8021BridgePortPriorityEntry
    MAX-ACCESS  not-accessible
    STATUS      current
    DESCRIPTION 
        "A list of Default User Priorities for each port of a 
         transparent bridge.  This is indexed by 
         ieee8021BridgeBasePortComponentId and ieee8021BridgeBasePort."
    AUGMENTS    { ieee8021BridgeBasePortEntry }
    ::= { ieee8021BridgePortPriorityTable 1 }

Ieee8021BridgePortPriorityEntry ::= SEQUENCE {
    ieee8021BridgePortDefaultUserPriority               IEEE8021PriorityValue,
    ieee8021BridgePortNumTrafficClasses                 Integer32,
    ieee8021BridgePortPriorityCodePointSelection        IEEE8021PriorityCodePoint,
    ieee8021BridgePortUseDEI                            TruthValue,
    ieee8021BridgePortRequireDropEncoding               TruthValue,
    ieee8021BridgePortServiceAccessPrioritySelection    TruthValue
}

ieee8021BridgePortDefaultUserPriority OBJECT-TYPE
    SYNTAX      IEEE8021PriorityValue
    MAX-ACCESS  read-write
    STATUS      current
    DESCRIPTION 
        "The default ingress User Priority for this port.  This only has 
         effect on media, such as Ethernet, that do not support native 
         User Priority.
         
         The value of this object MUST be retained across 
         reinitializations of the management system."
    ::= { ieee8021BridgePortPriorityEntry 1 }

ieee8021BridgePortNumTrafficClasses OBJECT-TYPE
    SYNTAX      Integer32
    MAX-ACCESS  read-write
    STATUS      current
    DESCRIPTION 
        "The number of egress traffic classes supported on this port.  
         This object may optionally be read-only.
         
         The value of this object MUST be retained across 
         reinitializations of the management system."
    ::= { ieee8021BridgePortPriorityEntry 2 }

ieee8021BridgePortPriorityCodePointSelection OBJECT-TYPE
    SYNTAX      IEEE8021PriorityCodePoint
    MAX-ACCESS  read-write
    STATUS      current
    DESCRIPTION 
        "This object identifies the rows in the PCP encoding and 
         decoding tables that are used to remark frames on this port if 
         this remarking is enabled."
    REFERENCE   
        "12.6.2.6, 12.6.2.7"
    ::= { ieee8021BridgePortPriorityEntry 3 }

ieee8021BridgePortUseDEI OBJECT-TYPE
    SYNTAX      TruthValue
    MAX-ACCESS  read-write
    STATUS      current
    DESCRIPTION 
        "If the Use DEI is set to true(1) for the port then the drop 
         eligible parameter is encoded in the DEI of transmitted frames, 
         and the drop eligible parameter shall be true(1) for a received 
         frame if the DEI is set in the VLAN tag or the Priority Code 
         Point Decoding Table indicates drop eligible True for the 
         received PCP value.  If the Use DEI parameter is false(2), the 
         DEI shall be transmitted as zero and ignored on receipt.  The 
         default value of the Use DEI parameter is false(2)."
    REFERENCE   
        "12.6.2.12, 12.6.2.13"
    ::= { ieee8021BridgePortPriorityEntry 4 }

ieee8021BridgePortRequireDropEncoding OBJECT-TYPE
    SYNTAX      TruthValue
    MAX-ACCESS  read-write
    STATUS      current
    DESCRIPTION 
        "If a Bridge supports encoding or deconding of drop eligible 
         from the PCP field of a VLAN tag (6.7.3) on any of its ports, 
         then it shall implement a Boolean parameter Require Drop 
         Encoding on each of its Ports with default value false(2).  If 
         Require Drop Encoding is True and the Bridge Port cannot encode 
         particular priorities with drop eligible, then frames queued 
         with those priorities and drop eligible true(1) shall be 
         discarded and not transmitted."
    REFERENCE   
        "12.6.2.14, 12.6.2.15"
    DEFVAL      { false }
    ::= { ieee8021BridgePortPriorityEntry 5 }

ieee8021BridgePortServiceAccessPrioritySelection OBJECT-TYPE
    SYNTAX      TruthValue
    MAX-ACCESS  read-write
    STATUS      current
    DESCRIPTION 
        "Indication of if the Service Access Priority Selection function 
         is supported on the Customer Bridge Port to request priority 
         handling of the frame from a Port-based service interface."
    REFERENCE   
        "12.6.2.16, 12.6.2.17"
    ::= { ieee8021BridgePortPriorityEntry 6 }

-- ============================================================
-- User Priority Regeneration Table
-- ============================================================

ieee8021BridgeUserPriorityRegenTable OBJECT-TYPE
    SYNTAX      SEQUENCE OF Ieee8021BridgeUserPriorityRegenEntry
    MAX-ACCESS  not-accessible
    STATUS      current
    DESCRIPTION 
        "A list of Regenerated User Priorities for each received User 
         Priority on each port of a bridge.  The Regenerated User 
         Priortiy value may be used to index the Traffic Class Table for 
         each input port.  This only has effect on media that support 
         native User Prioirty.  The default values for Regenerated User 
         Priorities are the same as the User Priorities."
    REFERENCE   
        "6.5"
    ::= { ieee8021BridgePriority 2 }

ieee8021BridgeUserPriorityRegenEntry OBJECT-TYPE
    SYNTAX      Ieee8021BridgeUserPriorityRegenEntry
    MAX-ACCESS  not-accessible
    STATUS      current
    DESCRIPTION 
        "A mapping of incoming User Priority to a Regenerated User 
         Priority."
    INDEX       { ieee8021BridgeBasePortComponentId, 
                  ieee8021BridgeBasePort, ieee8021BridgeUserPriority }
    ::= { ieee8021BridgeUserPriorityRegenTable 1 }

Ieee8021BridgeUserPriorityRegenEntry ::= SEQUENCE {
    ieee8021BridgeUserPriority          IEEE8021PriorityValue,
    ieee8021BridgeRegenUserPriority     IEEE8021PriorityValue
}

ieee8021BridgeUserPriority OBJECT-TYPE
    SYNTAX      IEEE8021PriorityValue
    MAX-ACCESS  not-accessible
    STATUS      current
    DESCRIPTION 
        "The User Priority for a frame received on this port."
    ::= { ieee8021BridgeUserPriorityRegenEntry 1 }

ieee8021BridgeRegenUserPriority OBJECT-TYPE
    SYNTAX      IEEE8021PriorityValue
    MAX-ACCESS  read-write
    STATUS      current
    DESCRIPTION 
        "The Regenerated User Priority that the incoming User Priority 
         is mapped to for this port.
         
         The value of this object MUST be retained across 
         reinitializations of the management system."
    ::= { ieee8021BridgeUserPriorityRegenEntry 2 }

-- ============================================================
-- Traffic Class Table
-- ============================================================

ieee8021BridgeTrafficClassTable OBJECT-TYPE
    SYNTAX      SEQUENCE OF Ieee8021BridgeTrafficClassEntry
    MAX-ACCESS  not-accessible
    STATUS      current
    DESCRIPTION 
        "A table mapping evaluated User Priority to Traffic Class, for 
         forwarding by the bridge.  Traffic class is a number in the 
         range (0..(ieee8021BridgePortNumTrafficClasses-1))."
    REFERENCE   
        "Table 8-3"
    ::= { ieee8021BridgePriority 3 }

ieee8021BridgeTrafficClassEntry OBJECT-TYPE
    SYNTAX      Ieee8021BridgeTrafficClassEntry
    MAX-ACCESS  not-accessible
    STATUS      current
    DESCRIPTION 
        "User Priority to Traffic Class mapping."
    INDEX       { ieee8021BridgeBasePortComponentId, 
                  ieee8021BridgeBasePort, 
                  ieee8021BridgeTrafficClassPriority }
    ::= { ieee8021BridgeTrafficClassTable 1 }

Ieee8021BridgeTrafficClassEntry ::= SEQUENCE {
    ieee8021BridgeTrafficClassPriority  IEEE8021PriorityValue,
    ieee8021BridgeTrafficClass          Integer32
}

ieee8021BridgeTrafficClassPriority OBJECT-TYPE
    SYNTAX      IEEE8021PriorityValue
    MAX-ACCESS  not-accessible
    STATUS      current
    DESCRIPTION 
        "The Priority value determined for the received frame.  This 
         value is equivalent to the priority indicated in the tagged 
         frame received, or one of the evaluated priorities, determined 
         according to media-type.  For untagged frames received from 
         Ethernet media, this value is equal to the 
         ieee8021BridgePortDefaultUserPriority value for the ingress 
         port.
         
         For untagged frames received from non-Ethernet media, this 
         value is equal to the ieee8021BridgeRegenUserPriority value for 
         the ingress port and media-specific user priority."
    ::= { ieee8021BridgeTrafficClassEntry 1 }

ieee8021BridgeTrafficClass OBJECT-TYPE
    SYNTAX      Integer32
    MAX-ACCESS  read-write
    STATUS      current
    DESCRIPTION 
        "The Traffic Class the received frame is mapped to.
         
         The value of this object MUST be retained across 
         reinitializations of the management system."
    ::= { ieee8021BridgeTrafficClassEntry 2 }


-- ============================================================
-- Outbound Access Priority Table
-- ============================================================

ieee8021BridgePortOutboundAccessPriorityTable OBJECT-TYPE
    SYNTAX      SEQUENCE OF Ieee8021BridgePortOutboundAccessPriorityEntry
    MAX-ACCESS  not-accessible
    STATUS      current
    DESCRIPTION 
        "A table mapping Regenerated User Priority to Outbound Access 
         Priority.  This is a fixed mapping for all port types, with two 
         options for 802.5 Token Ring, and three options for 802.17 RPR."
    REFERENCE   
        "Table 8-3"
    ::= { ieee8021BridgePriority 4 }

ieee8021BridgePortOutboundAccessPriorityEntry OBJECT-TYPE
    SYNTAX      Ieee8021BridgePortOutboundAccessPriorityEntry
    MAX-ACCESS  not-accessible
    STATUS      current
    DESCRIPTION 
        "Regenerated User Priority to Outbound Access Priority mapping."
    INDEX       { ieee8021BridgeBasePortComponentId, 
                  ieee8021BridgeBasePort, 
                  ieee8021BridgeRegenUserPriority }
    ::= { ieee8021BridgePortOutboundAccessPriorityTable 1 }

Ieee8021BridgePortOutboundAccessPriorityEntry ::= SEQUENCE {
    ieee8021BridgePortOutboundAccessPriority    IEEE8021PriorityValue
}

ieee8021BridgePortOutboundAccessPriority OBJECT-TYPE
    SYNTAX      IEEE8021PriorityValue
    MAX-ACCESS  read-only
    STATUS      current
    DESCRIPTION 
        "The Outbound Access Priority the received fram is mapped to."
    ::= { ieee8021BridgePortOutboundAccessPriorityEntry 1 }


-- ============================================================
-- ieee8021BridgePortDecodingTable
-- ============================================================

ieee8021BridgePortDecodingTable OBJECT-TYPE
    SYNTAX      SEQUENCE OF Ieee8021BridgePortDecodingEntry
    MAX-ACCESS  not-accessible
    STATUS      current
    DESCRIPTION 
        "A table that contains information about Priority Code Point 
         Decoding Table for a Port of a provider bridge.  Alternative 
         values for each table are specified as rows in Table 6-4 
         (6.7.3), with each alternative labeled by the number of 
         distinct priorities that can be communicated, and the number of 
         these for which drop precedence can be communicated.  All 
         writable objects in this table must be persistent over power up 
         restart/reboot."
    ::= { ieee8021BridgePriority 5 }

ieee8021BridgePortDecodingEntry OBJECT-TYPE
    SYNTAX      Ieee8021BridgePortDecodingEntry
    MAX-ACCESS  not-accessible
    STATUS      current
    DESCRIPTION 
        "A list of objects containing Priority Code Point Decoding 
         information for a port of a provider bridge."
    INDEX       { ieee8021BridgePortDecodingComponentId, 
                  ieee8021BridgePortDecodingPortNum, 
                  ieee8021BridgePortDecodingPriorityCodePointRow, 
                  ieee8021BridgePortDecodingPriorityCodePoint }
    ::= { ieee8021BridgePortDecodingTable 1 }

Ieee8021BridgePortDecodingEntry ::= SEQUENCE {
    ieee8021BridgePortDecodingComponentId           IEEE8021PbbComponentIdentifier,
    ieee8021BridgePortDecodingPortNum               IEEE8021BridgePortNumber,
    ieee8021BridgePortDecodingPriorityCodePointRow  IEEE8021PriorityCodePoint,
    ieee8021BridgePortDecodingPriorityCodePoint     Integer32,
    ieee8021BridgePortDecodingPriority              IEEE8021PriorityValue,
    ieee8021BridgePortDecodingDropEligible          TruthValue
}

ieee8021BridgePortDecodingComponentId OBJECT-TYPE
    SYNTAX      IEEE8021PbbComponentIdentifier
    MAX-ACCESS  not-accessible
    STATUS      current
    DESCRIPTION 
        "The component identifier is used to distinguish between the 
         multiple virtual bridge instances within a PBB.  In simple 
         situations where there is only a single component the default 
         value is 1."
    ::= { ieee8021BridgePortDecodingEntry 1 }

ieee8021BridgePortDecodingPortNum OBJECT-TYPE
    SYNTAX      IEEE8021BridgePortNumber
    MAX-ACCESS  not-accessible
    STATUS      current
    DESCRIPTION 
        "A unique identifier of a port controlled by this VLAN bridging 
         entity."
    ::= { ieee8021BridgePortDecodingEntry 2 }

ieee8021BridgePortDecodingPriorityCodePointRow OBJECT-TYPE
    SYNTAX      IEEE8021PriorityCodePoint
    MAX-ACCESS  not-accessible
    STATUS      current
    DESCRIPTION 
        "The specific row in Table 6-3 (6.7.3) indicating the PCP."
    ::= { ieee8021BridgePortDecodingEntry 3 }

ieee8021BridgePortDecodingPriorityCodePoint OBJECT-TYPE
    SYNTAX      Integer32 (0..7)
    MAX-ACCESS  not-accessible
    STATUS      current
    DESCRIPTION 
        "The specific PCP value in Table 6-3 (6.7.3)."
    ::= { ieee8021BridgePortDecodingEntry 4 }

ieee8021BridgePortDecodingPriority OBJECT-TYPE
    SYNTAX      IEEE8021PriorityValue
    MAX-ACCESS  read-write
    STATUS      current
    DESCRIPTION 
        "The specific priority value in Table 6-3 (6.7.3)."
    REFERENCE   
        "12.6.2.8, 12.6.2.9"
    ::= { ieee8021BridgePortDecodingEntry 5 }

ieee8021BridgePortDecodingDropEligible OBJECT-TYPE
    SYNTAX      TruthValue
    MAX-ACCESS  read-write
    STATUS      current
    DESCRIPTION 
        "The drop eligibility value in Table 6-3 (6.7.3)."
    REFERENCE   
        "12.6.2.8, 12.6.2.9"
    ::= { ieee8021BridgePortDecodingEntry 6 }

-- ============================================================
-- ieee8021BridgePortEncodingTable
-- ============================================================

ieee8021BridgePortEncodingTable OBJECT-TYPE
    SYNTAX      SEQUENCE OF Ieee8021BridgePortEncodingEntry
    MAX-ACCESS  not-accessible
    STATUS      current
    DESCRIPTION 
        "A table that contains information about Priority Code Point 
         Encoding Table for a Port of a provider bridge.  Alternative 
         values for each table are specified a rows in Table 6-3 
         (6.7.3), with each alternative labeled by the number of 
         distinct priorities that can be communicated, and the number of 
         these for which drop precedence can be communicated.  All 
         writable objects in this table must be persistent over power up 
         restart/reboot."
    ::= { ieee8021BridgePriority 6 }

ieee8021BridgePortEncodingEntry OBJECT-TYPE
    SYNTAX      Ieee8021BridgePortEncodingEntry
    MAX-ACCESS  not-accessible
    STATUS      current
    DESCRIPTION 
        "A list of objects containing Priority Code Point Encoding 
         information for a port of a provider bridge."
    INDEX       { ieee8021BridgePortEncodingComponentId, 
                  ieee8021BridgePortEncodingPortNum, 
                  ieee8021BridgePortEncodingPriorityCodePointRow, 
                  ieee8021BridgePortEncodingPriorityCodePoint, 
                  ieee8021BridgePortEncodingDropEligible }
    ::= { ieee8021BridgePortEncodingTable 1 }

Ieee8021BridgePortEncodingEntry ::= SEQUENCE {
    ieee8021BridgePortEncodingComponentId           IEEE8021PbbComponentIdentifier,
    ieee8021BridgePortEncodingPortNum               IEEE8021BridgePortNumber,
    ieee8021BridgePortEncodingPriorityCodePointRow  IEEE8021PriorityCodePoint,
    ieee8021BridgePortEncodingPriorityCodePoint     Integer32,
    ieee8021BridgePortEncodingDropEligible          TruthValue,
    ieee8021BridgePortEncodingPriority              IEEE8021PriorityValue
}

ieee8021BridgePortEncodingComponentId OBJECT-TYPE
    SYNTAX      IEEE8021PbbComponentIdentifier
    MAX-ACCESS  not-accessible
    STATUS      current
    DESCRIPTION 
        "The component identifier is used to distinguish between the 
         multiple virtual bridge instances within a PBB.  In simple 
         situations where there is only a single component the default 
         values is 1."
    ::= { ieee8021BridgePortEncodingEntry 1 }

ieee8021BridgePortEncodingPortNum OBJECT-TYPE
    SYNTAX      IEEE8021BridgePortNumber
    MAX-ACCESS  not-accessible
    STATUS      current
    DESCRIPTION 
        "A unique identifier of a port controlled by this VLAN bridging 
         entit."
    ::= { ieee8021BridgePortEncodingEntry 2 }

ieee8021BridgePortEncodingPriorityCodePointRow OBJECT-TYPE
    SYNTAX      IEEE8021PriorityCodePoint
    MAX-ACCESS  not-accessible
    STATUS      current
    DESCRIPTION 
        "The specific row in Table 6-3 (6.7.3) indicating the PCP row 
         (i.e. 8P0D, 7P1D, 6P2D, 5P3D)."
    ::= { ieee8021BridgePortEncodingEntry 3 }

ieee8021BridgePortEncodingPriorityCodePoint OBJECT-TYPE
    SYNTAX      Integer32 (0..7)
    MAX-ACCESS  not-accessible
    STATUS      current
    DESCRIPTION 
        "The specific row in Table 6-3 (6.7.3) indicating the PCP (i.e, 
         0, 1, 2, 3, 4, 5, 6, 7)."
    ::= { ieee8021BridgePortEncodingEntry 4 }

ieee8021BridgePortEncodingDropEligible OBJECT-TYPE
    SYNTAX      TruthValue
    MAX-ACCESS  not-accessible
    STATUS      current
    DESCRIPTION 
        "The specific row in Table 6-3 (6.7.3) indicating the drop 
         eligibility.  A value of true(1) means eligible for drop."
    ::= { ieee8021BridgePortEncodingEntry 5 }

ieee8021BridgePortEncodingPriority OBJECT-TYPE
    SYNTAX      IEEE8021PriorityValue
    MAX-ACCESS  read-write
    STATUS      current
    DESCRIPTION 
        "The encoding priority in Table 6-3 (6.7.3)."
    REFERENCE   
        "12.6.2.10, 12.6.2.11"
    ::= { ieee8021BridgePortEncodingEntry 6 }


-- ============================================================
-- ieee88021BridgeServiceAccessPriorityTable
-- ============================================================

ieee8031BridgeServiceAccessPriorityTable OBJECT-TYPE
    SYNTAX      SEQUENCE OF Ieee8031BridgeServiceAccessPriorityEntry
    MAX-ACCESS  not-accessible
    STATUS      current
    DESCRIPTION 
        "A table that contains information about the Service Access 
         Priority Selection function for a provider bridge.  The use of 
         this table enables a mechanism for a Customer Bridge attached 
         to a Provider Bridged Network to request priority handling of 
         frames.  All writable objects in this table must be persisitent 
         over power up restart/reboot."
    ::= { ieee8021BridgePriority 7 }

ieee8031BridgeServiceAccessPriorityEntry OBJECT-TYPE
    SYNTAX      Ieee8031BridgeServiceAccessPriorityEntry
    MAX-ACCESS  not-accessible
    STATUS      current
    DESCRIPTION 
        "A list of objects contiaining information about the Service 
         Access Priority Selection function for a provider bridge."
    INDEX       { ieee8021BridgeServiceAccessPriorityComponentId, 
                  ieee8021BridgeServiceAccessPriorityPortNum, 
                  ieee8021BridgeServiceAccessPriorityReceived }
    ::= { ieee8031BridgeServiceAccessPriorityTable 1 }

Ieee8031BridgeServiceAccessPriorityEntry ::= SEQUENCE {
    ieee8021BridgeServiceAccessPriorityComponentId  IEEE8021PbbComponentIdentifier,
    ieee8021BridgeServiceAccessPriorityPortNum      IEEE8021BridgePortNumber,
    ieee8021BridgeServiceAccessPriorityReceived     IEEE8021PriorityValue,
    ieee8021BridgeServiceAccessPriorityValue        IEEE8021PriorityValue
}

ieee8021BridgeServiceAccessPriorityComponentId OBJECT-TYPE
    SYNTAX      IEEE8021PbbComponentIdentifier
    MAX-ACCESS  not-accessible
    STATUS      current
    DESCRIPTION 
        "The component identifier is used to distinguish between the 
         multiple virtual brige instances within a PBB.  In simple 
         situtations where there is only a signle component the default 
         values is 1."
    ::= { ieee8031BridgeServiceAccessPriorityEntry 1 }

ieee8021BridgeServiceAccessPriorityPortNum OBJECT-TYPE
    SYNTAX      IEEE8021BridgePortNumber
    MAX-ACCESS  not-accessible
    STATUS      current
    DESCRIPTION 
        "A unique identifier of a port controlled by this VALN bridging 
         entity."
    ::= { ieee8031BridgeServiceAccessPriorityEntry 2 }

ieee8021BridgeServiceAccessPriorityReceived OBJECT-TYPE
    SYNTAX      IEEE8021PriorityValue
    MAX-ACCESS  not-accessible
    STATUS      current
    DESCRIPTION 
        "The default received priority  value in Table 6-3 (6.7.3): 
         (i.e., 0,1,2,3,4,5,6,7)."
    ::= { ieee8031BridgeServiceAccessPriorityEntry 3 }

ieee8021BridgeServiceAccessPriorityValue OBJECT-TYPE
    SYNTAX      IEEE8021PriorityValue
    MAX-ACCESS  read-write
    STATUS      current
    DESCRIPTION 
        "The regenerated priority  value in Table 6-3 (6.7.3): (i.e., 
         0,1,2,3,4,5,6,7)."
    REFERENCE   
        "12.6.2.19, 12.6.2.19"
    ::= { ieee8031BridgeServiceAccessPriorityEntry 4 }

-- ============================================================
-- the ieee8021BridgeMrp subtree
-- ============================================================

ieee8021BridgeMrp OBJECT IDENTIFIER
    ::= { ieee8021BridgeObjects 4 }

-- ============================================================
-- The MRP Port Table
-- ============================================================

ieee8021BridgePortMrpTable OBJECT-TYPE
    SYNTAX      SEQUENCE OF Ieee8021BridgePortMrpEntry
    MAX-ACCESS  not-accessible
    STATUS      current
    DESCRIPTION 
        "A table of MRP control information about every bridge port.  
         This is indexed by ieee8021BridgeBasePortComponentId and 
         ieee8021BridgeBasePort."
    ::= { ieee8021BridgeMrp 1 }

ieee8021BridgePortMrpEntry OBJECT-TYPE
    SYNTAX      Ieee8021BridgePortMrpEntry
    MAX-ACCESS  not-accessible
    STATUS      current
    DESCRIPTION 
        "MRP control information for a bridge port."
    AUGMENTS    { ieee8021BridgeBasePortEntry }
    ::= { ieee8021BridgePortMrpTable 1 }

Ieee8021BridgePortMrpEntry ::= SEQUENCE {
    ieee8021BridgePortMrpJoinTime       TimeInterval,
    ieee8021BridgePortMrpLeaveTime      TimeInterval,
    ieee8021BridgePortMrpLeaveAllTime   TimeInterval
}

ieee8021BridgePortMrpJoinTime OBJECT-TYPE
    SYNTAX      TimeInterval
    MAX-ACCESS  read-write
    STATUS      current
    DESCRIPTION 
        "The MRP Join time, in centiseconds.
         
         The valu of this object MUST be retained across 
         reinitializations of the management system."
    DEFVAL      { 20 }
    ::= { ieee8021BridgePortMrpEntry 1 }

ieee8021BridgePortMrpLeaveTime OBJECT-TYPE
    SYNTAX      TimeInterval
    MAX-ACCESS  read-write
    STATUS      current
    DESCRIPTION 
        "The MRP Leave time, in centiseconds.
         
         The value of this object MUST be retained across 
         reinitializations of the management system."
    DEFVAL      { 60 }
    ::= { ieee8021BridgePortMrpEntry 2 }

ieee8021BridgePortMrpLeaveAllTime OBJECT-TYPE
    SYNTAX      TimeInterval
    MAX-ACCESS  read-write
    STATUS      current
    DESCRIPTION 
        "The MRB LeaveALL time, in centiseconds.
         
         The value of this object MUST be retained across 
         reinitializations of the msnagement system."
    DEFVAL      { 1000 }
    ::= { ieee8021BridgePortMrpEntry 3 }

-- ============================================================
-- The MMRP Port Configuration and Status Table
-- ============================================================

ieee8021BridgeMmrp OBJECT IDENTIFIER
    ::= { ieee8021BridgeObjects 5 }

ieee8021BridgePortMmrpTable OBJECT-TYPE
    SYNTAX      SEQUENCE OF Ieee8021BridgePortMmrpEntry
    MAX-ACCESS  not-accessible
    STATUS      current
    DESCRIPTION 
        "A table of MMRP control and status information about every 
         bridge port.  Augements the ieee8021BridgeBasePortTable."
    ::= { ieee8021BridgeMmrp 1 }

ieee8021BridgePortMmrpEntry OBJECT-TYPE
    SYNTAX      Ieee8021BridgePortMmrpEntry
    MAX-ACCESS  not-accessible
    STATUS      current
    DESCRIPTION 
        "MMRP control and status information for a bridge port."
    AUGMENTS    { ieee8021BridgeBasePortEntry }
    ::= { ieee8021BridgePortMmrpTable 1 }

Ieee8021BridgePortMmrpEntry ::= SEQUENCE {
    ieee8021BridgePortMmrpEnabledStatus                 TruthValue,
    ieee8021BridgePortMmrpFailedRegistrations           Counter64,
    ieee8021BridgePortMmrpLastPduOrigin                 MacAddress,
    ieee8021BridgePortMmrpRestrictedGroupRegistration   TruthValue
}

ieee8021BridgePortMmrpEnabledStatus OBJECT-TYPE
    SYNTAX      TruthValue
    MAX-ACCESS  read-write
    STATUS      current
    DESCRIPTION 
        "The administrative state of MMRP operation on this port.  The 
         value true(1) indicates that MMRP is enabled on this port in 
         all VLANs as long as ieee8021BridgeMmrpEnabledStatus is also 
         true(1).  A value of false(2) indicates that MMRP is disabled 
         on this port in all VLANs: any MMRP packets received will be 
         silently discarded, and no MMRP registrations will be 
         propagated from other ports.  Setting this to a value of 
         true(1) will be stored by the agetn but will only take aeffect 
         on the MMRP protocol operation if 
         ieee8021BridgeMmrpEnabledStatus also indicates the value 
         true(1).  This object affects all MMRP Applicant and Register 
         state machines on this port.  A transition from false(2) to 
         true(1) will cause a reset ofa ll MMRP state machines on this 
         port.
         
         The value of this object MUST be retained across 
         reinitializations of the management system."
    DEFVAL      { true }
    ::= { ieee8021BridgePortMmrpEntry 1 }

ieee8021BridgePortMmrpFailedRegistrations OBJECT-TYPE
    SYNTAX      Counter64
    MAX-ACCESS  read-only
    STATUS      current
    DESCRIPTION 
        "The total number of failed MMRP registrations, for any reason, 
         in all VLANs, on this port."
    ::= { ieee8021BridgePortMmrpEntry 2 }

ieee8021BridgePortMmrpLastPduOrigin OBJECT-TYPE
    SYNTAX      MacAddress
    MAX-ACCESS  read-write
    STATUS      current
    DESCRIPTION 
        "The Source MAC Address of the last MMRP message received on 
         this port."
    ::= { ieee8021BridgePortMmrpEntry 3 }

ieee8021BridgePortMmrpRestrictedGroupRegistration OBJECT-TYPE
    SYNTAX      TruthValue
    MAX-ACCESS  read-write
    STATUS      current
    DESCRIPTION 
        "The stat of Restricted Group Registration on this port.  If the 
         value of this control is true(1), then creation of a new 
         dynamic entry is permitted only if there is a Static Filtering 
         Entry for the VLAN concerned, in which the Registrar 
         Administrative Control value is Normal Registration.
         
         The value of this object MUST be retained across 
         reinitializations of the management system."
    REFERENCE   
        "11.2.3.2.3, 12.11.1.3"
    DEFVAL      { false }
    ::= { ieee8021BridgePortMmrpEntry 4 }

-- ============================================================
-- I-LAN Interface configuration table
-- ============================================================

ieee8021BridgeInternalLan OBJECT IDENTIFIER
    ::= { ieee8021BridgeObjects 6 }

ieee8021BridegILanIfTable OBJECT-TYPE
    SYNTAX      SEQUENCE OF Ieee8021BridegILanIfEntry
    MAX-ACCESS  not-accessible
    STATUS      current
    DESCRIPTION 
        "This table is a sparse augmentation of ifTable and controls the 
         creation of the I-LAN Interface.  An I-LAN Interface is used to 
         create internal connections between bridge ports in a 802.1 
         device.  An I-LAN Interfaces can be directly associated with a 
         set of bridge ports.  An I-LAN Interfaces can also be used as a 
         stacking interface to relate other interfaces before 
         association to bridge ports.
         
         For example, an I-LAN interface can be created to link traffic 
         between a PIP and a CBP.  In this case a CBP is created on the 
         B-Component and the CBP's related IfEntry is stacked upon the 
         IfEntry of the I-LAN.  The PIP is stacked upon the I-LAN using 
         the IfStackTable.  Finally, a VIP is created on the I-Component 
         and is associated with the PIP, thus completing the pat from 
         the I-Component's MAC relay to the CBP on the B-Component.
         
         Entries in this table must be persistent over power up 
         restart/reboot."
    REFERENCE   
        "17.3.2.2"
    ::= { ieee8021BridgeInternalLan 1 }

ieee8021BridegILanIfEntry OBJECT-TYPE
    SYNTAX      Ieee8021BridegILanIfEntry
    MAX-ACCESS  not-accessible
    STATUS      current
    DESCRIPTION 
        "Each entry consists of a Row Status to control creation."
    INDEX       { ifIndex }
    ::= { ieee8021BridegILanIfTable 1 }

Ieee8021BridegILanIfEntry ::= SEQUENCE {
    ieee8021BridgeILanIfRowStatus   RowStatus
}

ieee8021BridgeILanIfRowStatus OBJECT-TYPE
    SYNTAX      RowStatus
    MAX-ACCESS  read-create
    STATUS      current
    DESCRIPTION 
        "This object is used to create and delete entries in this table 
         and the Interface table."
    ::= { ieee8021BridegILanIfEntry 1 }

-- ============================================================
-- 802.1D Dynamic Port Creation table
-- ============================================================

ieee8021BridgeDot1d OBJECT IDENTIFIER
    ::= { ieee8021BridgeObjects 7 }

ieee8021BridgeDot1dPortTable OBJECT-TYPE
    SYNTAX      SEQUENCE OF Ieee8021BridgeDot1dPortEntry
    MAX-ACCESS  not-accessible
    STATUS      current
    DESCRIPTION 
        "This table provides the capability to dynamically create and 
         delete 802.1D bridge ports.  Each entry in this table must have 
         a corresponding entry int he ieee8021BridgeBasePortTable.
         
         Entries in this table must be persistent over power up 
         restart/reboot."
    REFERENCE   
        "17.5.3"
    ::= { ieee8021BridgeDot1d 1 }

ieee8021BridgeDot1dPortEntry OBJECT-TYPE
    SYNTAX      Ieee8021BridgeDot1dPortEntry
    MAX-ACCESS  not-accessible
    STATUS      current
    DESCRIPTION 
        "Each entry consists of a Row Status to control creation."
    INDEX       { ieee8021BridgeBasePortComponentId, 
                  ieee8021BridgeBasePort }
    ::= { ieee8021BridgeDot1dPortTable 1 }

Ieee8021BridgeDot1dPortEntry ::= SEQUENCE {
    ieee8021BridgeDot1dPortRowStatus    RowStatus
}

ieee8021BridgeDot1dPortRowStatus OBJECT-TYPE
    SYNTAX      RowStatus
    MAX-ACCESS  read-create
    STATUS      current
    DESCRIPTION 
        "This object is used to create and delete entries in this table 
         and the ieee8021BridgeBasePortTable."
    ::= { ieee8021BridgeDot1dPortEntry 1 }

-- ============================================================
-- IEEE 802.1D MIB - Conformance Information
-- ============================================================

ieee8021BridgeConformance OBJECT IDENTIFIER
    ::= { ieee8021BridgeMib 2 }

ieee8021BridgeCompliances OBJECT IDENTIFIER
    ::= { ieee8021BridgeConformance 1 }

ieee8021BridgeGroups OBJECT IDENTIFIER
    ::= { ieee8021BridgeConformance 2 }

-- ============================================================
-- unites of conformance
-- ============================================================

-- ============================================================
-- the ieee8021BridgeBase group
-- ============================================================

ieee8021BridgeBaseBridgeGroup OBJECT-GROUP
    OBJECTS     { ieee8021BridgeBaseBridgeAddress, 
                  ieee8021BridgeBaseNumPorts, 
                  ieee8021BridgeBaseComponentType }
    STATUS      current
    DESCRIPTION 
        "Bridge level information for this device."
    ::= { ieee8021BridgeGroups 1 }

ieee8021BridgeBasePortGroup OBJECT-GROUP
    OBJECTS     { ieee8021BridgeBasePortIfIndex, 
                  ieee8021BridgeBasePortDelayExceededDiscards, 
                  ieee8021BridgeBasePortMtuExceededDiscards, 
                  ieee8021BridgeBasePortType, 
                  ieee8021BridgeBasePortExternal, 
                  ieee8021BridgeBasePortAdminPointToPoint, 
                  ieee8021BridgeBasePortOperPointToPoint, 
                  ieee8021BridgeBasePortName }
    STATUS      current
    DESCRIPTION 
        "Information for each port on this device."
    ::= { ieee8021BridgeGroups 2 }

ieee8021BridgeBaseCapGroup OBJECT-GROUP
    OBJECTS     { ieee8021BridgeBaseDeviceCapabilities, 
                  ieee8021BridgeBasePortCapabilities, 
                  ieee8021BridgeBasePortTypeCapabilities }
    STATUS      current
    DESCRIPTION 
        "A collection of objects indicating the optional capabilities of 
         the device."
    ::= { ieee8021BridgeGroups 3 }

ieee8021BridgeDeviceMmrpGroup OBJECT-GROUP
    OBJECTS     { ieee8021BridgeBaseMmrpEnabledStatus }
    STATUS      current
    DESCRIPTION 
        "A collection of objects provided device-level control for 
         Multicast Filtering extended bridge services."
    ::= { ieee8021BridgeGroups 4 }

-- ============================================================
-- the ieee8021BridgeTp group
-- ============================================================

ieee8021BridgeTpPortGroup OBJECT-GROUP
    OBJECTS     { ieee8021BridgeTpPortPortMaxInfo, 
                  ieee8021BridgeTpPortInFrames, 
                  ieee8021BridgeTpPortOutFrames, 
                  ieee8021BridgeTpPortInDiscards }
    STATUS      current
    DESCRIPTION 
        "Dynamic Filtering Database information for each port of the 
         Bridge."
    ::= { ieee8021BridgeGroups 6 }

-- ============================================================
-- Bridge Priority groups
-- ============================================================

ieee8021BridgeDevicePriorityGroup OBJECT-GROUP
    OBJECTS     { ieee8021BridgeBaseTrafficClassesEnabled }
    STATUS      current
    DESCRIPTION 
        "A collcation of objects providing device-level control for the 
         Priority services."
    ::= { ieee8021BridgeGroups 7 }

ieee8021BridgeDefaultPriorityGroup OBJECT-GROUP
    OBJECTS     { ieee8021BridgePortDefaultUserPriority, 
                  ieee8021BridgePortPriorityCodePointSelection, 
                  ieee8021BridgePortUseDEI, 
                  ieee8021BridgePortRequireDropEncoding, 
                  ieee8021BridgePortServiceAccessPrioritySelection }
    STATUS      current
    DESCRIPTION 
        "A collection of objects defining the User Priority applicable 
         to each port for media that do not support native User 
         Priority."
    ::= { ieee8021BridgeGroups 8 }

ieee8021BridgeRegenPriorityGroup OBJECT-GROUP
    OBJECTS     { ieee8021BridgeRegenUserPriority }
    STATUS      current
    DESCRIPTION 
        "A collection of objects defining the User Priorities applicable 
         to each port for media that support native User Priority."
    ::= { ieee8021BridgeGroups 9 }

ieee8021BridgePriorityGroup OBJECT-GROUP
    OBJECTS     { ieee8021BridgePortNumTrafficClasses, 
                  ieee8021BridgeTrafficClass }
    STATUS      current
    DESCRIPTION 
        "A collection of objects defining the traffic classses within a 
         bridge for each evaluated User Priority."
    ::= { ieee8021BridgeGroups 10 }

ieee8021BridgeAccessPriorityGroup OBJECT-GROUP
    OBJECTS     { ieee8021BridgePortOutboundAccessPriority }
    STATUS      current
    DESCRIPTION 
        "A collection of objects defining the media-dependent outbound 
         access level for each priority."
    ::= { ieee8021BridgeGroups 11 }

ieee8021BridgePortMrpGroup OBJECT-GROUP
    OBJECTS     { ieee8021BridgePortMrpJoinTime, 
                  ieee8021BridgePortMrpLeaveTime, 
                  ieee8021BridgePortMrpLeaveAllTime }
    STATUS      current
    DESCRIPTION 
        "A collection of objects providing port level control and status 
         information for MRP operation."
    ::= { ieee8021BridgeGroups 12 }

ieee8021BridgePortMmrpGroup OBJECT-GROUP
    OBJECTS     { ieee8021BridgePortMmrpEnabledStatus, 
                  ieee8021BridgePortMmrpFailedRegistrations, 
                  ieee8021BridgePortMmrpLastPduOrigin, 
                  ieee8021BridgePortMmrpRestrictedGroupRegistration }
    STATUS      current
    DESCRIPTION 
        "A collection of objects providing port level control and status 
         information for MMRP operation."
    ::= { ieee8021BridgeGroups 13 }

ieee8021BridgePortDecodingGroup OBJECT-GROUP
    OBJECTS     { ieee8021BridgePortDecodingPriority, 
                  ieee8021BridgePortDecodingDropEligible }
    STATUS      current
    DESCRIPTION 
        "A collection of objects providing statistics counters for 
         decoding priority and drop eligibility for bridge ports."
    ::= { ieee8021BridgeGroups 14 }

ieee8021BridgePortEncodingGroup OBJECT-GROUP
    OBJECTS     { ieee8021BridgePortEncodingPriority }
    STATUS      current
    DESCRIPTION 
        "A collection of objects providing statistics counters for 
         encoding prioirty and drop eligibility for bridge ports."
    ::= { ieee8021BridgeGroups 15 }

ieee8021BridgeServiceAccessPriorityGroup OBJECT-GROUP
    OBJECTS     { ieee8021BridgeServiceAccessPriorityValue }
    STATUS      current
    DESCRIPTION 
        "A collection of objects providing statistics  counters for 
         service access priority."
    ::= { ieee8021BridgeGroups 16 }

-- ============================================================
-- Internal LAN group
-- ============================================================

ieee8021BridgeInternalLANGroup OBJECT-GROUP
    OBJECTS     { ieee8021BridgeILanIfRowStatus }
    STATUS      current
    DESCRIPTION 
        "A collection of objects providing control of internal LAN 
         configuration."
    ::= { ieee8021BridgeGroups 17 }


-- ============================================================
-- Bridge Creation Group
-- ============================================================

ieee8021BridgeCreatableBaseBridgeGroup OBJECT-GROUP
    OBJECTS     { ieee8021BridgeBaseRowStatus }
    STATUS      current
    DESCRIPTION 
        "Controls the management system directed creation of Bridge 
         Components."
    ::= { ieee8021BridgeGroups 18 }

-- ============================================================
-- Dot1d Dynamic Port Creation group
-- ============================================================

ieee8021BridgeDot1dDynamicPortCreationGroup OBJECT-GROUP
    OBJECTS     { ieee8021BridgeDot1dPortRowStatus }
    STATUS      current
    DESCRIPTION 
        "A collection of objects providing dynamic creation and deletion 
         of 802.1D bridge ports."
    ::= { ieee8021BridgeGroups 19 }

-- ============================================================
-- compliance statements
-- ============================================================

ieee8021BridgeCompliance MODULE-COMPLIANCE
    STATUS      current
    DESCRIPTION 
        "The compliance statement for devices supporting bridging 
         services as defined in 802.1D-2004.  Such devices support path 
         cost values of 32-bits, and bridge and port priority values are 
         more restricted thatn in 802.1D-1995.
         
         Full support for the 802.1D management objects requires 
         implementation of the objects listed in the systemGroup from 
         the SNMPv2-MIB [RFC3418], as well as the objects listed in the 
         ifGeneralInformationGroup from the IF-MIB [RFC2863]."

    MODULE      -- this module

        MANDATORY-GROUPS        { ieee8021BridgeBaseBridgeGroup, 
                  ieee8021BridgeBasePortGroup }

        GROUP   ieee8021BridgeCreatableBaseBridgeGroup
        DESCRIPTION   
              "Implementation of this group is mandatory for bridges that 
               allow management systems to add and delete bridge 
               components.  Provider Backbone Edge Bridges sould typically 
               fall in this category."

        GROUP   ieee8021BridgeTpPortGroup
        DESCRIPTION   
              "Implementation of this group is mandatory for bridges that 
               suppport the transparent bridging mode.  A transparent 
               bridge will implement this group."

        GROUP   ieee8021BridgeInternalLANGroup
        DESCRIPTION   
              "Implementation of this group is optional.  It can be 
               supported to provide control over the relationship between 
               interfaces and bridge ports where such relationships are 
               more complex than a simple 1-to-1 mapping."

        GROUP   ieee8021BridgeDot1dDynamicPortCreationGroup
        DESCRIPTION   
              "Implementation of this group is optional.  It can be 
               supported to provide the ability to dynamically create and 
               delete 802.1D bridge ports."

    MODULE      SNMPv2-MIB

        MANDATORY-GROUPS        { systemGroup }

    MODULE      IF-MIB

        MANDATORY-GROUPS        { ifGeneralInformationGroup }

    ::= { ieee8021BridgeCompliances 1 }

ieee8021BridgePriorityAndMulticastFilteringCompliance MODULE-COMPLIANCE
    STATUS      deprecated
    DESCRIPTION 
        "The compliance statement for device support of Priority and 
         Multicast Filtering extended bridging services."

    MODULE      -- this module

        MANDATORY-GROUPS        { ieee8021BridgeCapGroup }

        GROUP   ieee8021BridgeDeviceMmrpGroup
        DESCRIPTION   
              "This group is mandatory for devices supporting the MMRP 
               application, defined by IEEE 802.1D Extended Filtering 
               Services."

        GROUP   ieee8021BridgeDevicePriorityGroup
        DESCRIPTION   
              "This group is mandatory only for devices supporting the 
               priority forwarding operations defined by IEEE 802.1D."

        GROUP   ieee8021BridgeDefaultPriorityGroup
        DESCRIPTION   
              "This group is mandatory only for devices supporting the 
               priority forwarding operations defined by the extended 
               bridge services with media types, such as Ethernet, that do 
               not support native User Priority."

        GROUP   ieee8021BridgeRegenPriorityGroup
        DESCRIPTION   
              "This group is mandatory only for devices supporting the 
               prioirty forwarding operations defined by IEEE 802.1D and 
               that have interface media types that support native User 
               Priority, e.g., IEEE 802.5."

        GROUP   ieee8021BridgePriorityGroup
        DESCRIPTION   
              "This group is mandatory only for devices supporting the 
               priority forwarding operations defined by IEEE 802.1D."

        GROUP   ieee8021BridgeAccessPriorityGroup
        DESCRIPTION   
              "This group is optioanl and is relevant only for devices 
               supporting the priority forwarding operations defined by 
               IEEE 802.1D and that have interface media types that 
               support native Access Priority, e.g., IEEE 802.5."

        GROUP   ieee8021BridgePortMrpGroup
        DESCRIPTION   
              "This group is mandatory for devices supporting nay of the 
               MRP applications: e.g., MMRP, defined by the extended 
               filtering services of 802.1D; or MVRP, defined by 802.1Q 
               (refer to the Q-BRIDGE-MIB for conformance statements for 
               MVRP)."

        GROUP   ieee8021BridgePortMmrpGroup
        DESCRIPTION   
              "This group is mandatory for devices supporting the MMRP 
               application, as adefined by IEEE 802.1D Extended Filtering 
               Services."

        GROUP   ieee8021BridgePortDecodingGroup
        DESCRIPTION   
              "This group is optional and supports Priority Code Point 
               Decoding Table for a Port of a provider bridge."

        GROUP   ieee8021BridgePortEncodingGroup
        DESCRIPTION   
              "This group is optional and supports Priority Code Point 
               Encoding Table for a Port of a provider bridge."

        GROUP   ieee8021BridgeServiceAccessPriorityGroup
        DESCRIPTION   
              "This group is optional and supports Priority Code Point 
               Encoding Table for a Port of a provider bridge."

        OBJECT  ieee8021BridgePortNumTrafficClasses
        MIN-ACCESS  read-only
        DESCRIPTION   
              "Write access is not required."

        OBJECT  ieee8021BridgeTrafficClass
        MIN-ACCESS  read-only
        DESCRIPTION   
              "Write access is not required."

        OBJECT  ieee8021BridgeRegenUserPriority
        MIN-ACCESS  read-only
        DESCRIPTION   
              "Write access is not required."

    ::= { ieee8021BridgeCompliances 2 }

END -- end of module IEEE8021-BRIDGE-MIB.

-- vim: ft=mib comments=\f\:\",\b\:\-\-,\:\-\-,\f\b\:- fo+=tcqlornw tw=72 nocin nosi sts=4 sw=4
